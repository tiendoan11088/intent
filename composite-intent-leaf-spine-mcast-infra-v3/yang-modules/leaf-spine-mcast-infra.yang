module leaf-spine-mcast-infra {
  yang-version 1.1;
  namespace "http://www.nokia.com/management-solutions/leaf-spine-mcast-infra";
  prefix cmp;

  import webfwk-ui-metadata {
    prefix ui;
  }

  revision 2023-11-01 {
    description
      "Update cp-leaf-name leaf to node-id leaf and update uni-id leaf to lag-label leaf";
  }
  
  revision 2023-05-25 {
    description
      "Generated by Nokia";
  }

  container leaf-spine-mcast-infra {
    config true;
    
    leaf node-id {
      type string;
      description
        "Network Leaf Node Id";
      ui:i18n-text "Node Id";
      ui:order "1";
      ui:suggest "suggestCpLeafName";
    }

    leaf lag-description {
      type string;
      description
        "LAG Description";
      ui:i18n-text "LAG Description";
      ui:order "2";
      ui:suggest "suggestNniIds";
    }
    
    leaf c-vlan-id {
      type uint16 {
        range "2..4090 | 4092..4094";
      }
      description
        "C-VLAN ID";
      ui:order "3";
      ui:i18n-text "C-VLAN ID";
      ui:global-search-category "C-VLAN";
      ui:maps-to-child-intent "l2-infra-access";
      ui:suggest "suggestCVlanIds";
    }

    leaf service-profile {
      type string;
      mandatory true;
      description
        "The Service Profile";
      ui:i18n-text "Network User Service Profile";
      ui:order "4";
      ui:suggest "suggestUserServiceProfileNames";
      // ui:link-to-profile {
      //   ui:type "user-service-profile";
      //   ui:subtype-auto-detect;
      // }
    }
  }
}
